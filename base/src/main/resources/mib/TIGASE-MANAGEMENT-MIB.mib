--
-- @(#)TIGASE-MANAGEMENT-MIB.mib	1.0 09/01/09
--
-- Copyright 2009 Tigase.org, All rights reserved.
--
-- The TIGASE-MANAGEMENT-MIB Module
--
-- See tigaseManagementMIB MODULE-IDENTITY for a description overview.
-- See conformance statements for mandatory objects
--

TIGASE-MANAGEMENT-MIB DEFINITIONS ::= BEGIN

IMPORTS
    MODULE-IDENTITY, OBJECT-TYPE, NOTIFICATION-TYPE, Counter32, Gauge32,
	Integer32, Counter64, enterprises
        FROM SNMPv2-SMI
    DisplayString, TEXTUAL-CONVENTION, RowPointer
        FROM SNMPv2-TC
    MODULE-COMPLIANCE, OBJECT-GROUP, NOTIFICATION-GROUP
        FROM SNMPv2-CONF;

-- Module Identity
------------------

tigaseMgtMIB MODULE-IDENTITY
    LAST-UPDATED "200901091416Z"
    -- Format is "YYYYMMDDhhmmZ"
    ORGANIZATION "Tigase.org"
    CONTACT-INFO "Tigase.org
                  87 Mayfield Way
		  CB23 5JA Cambourne, UK
		  http://www.tigase.org
		  or contact your local support representative"
    DESCRIPTION
            "Copyright Tigase.org All rights reserved.

             This module defines the MIB that provides access to the
	     Tigase Server monitoring data.
	     This module is derived from the Java[tm] programming language APIs
             described in the java.lang.management package of
             Java[tm] 2, Standard Edition, 5.0.

	     See the Java programming language APIs of JSR 163 for
             'Monitoring and Management of the Java[TM] Virtual Machine'
             for more details.

	     Where the Java programming language API uses long, or int,
             the MIB often uses the corresponding unsigned quantity -
             which is closer to the object semantics.

             In those cases, it often happens that the -1 value that might
             be used by the API to indicate an unknown/unimplemented
             value cannot be used. Instead the MIB uses the value 0, which
             stricly speaking cannot be distinguished from a valid value.
             In many cases however, a running system will have non-zero
             values, so using 0 instead of -1 to indicate an unknown
             quantity does not lose any functionality.
	    "
    REVISION     "200901141416Z"
    -- Format is "YYYYMMDDhhmmZ"
    DESCRIPTION
            "
            TIGASE-MANAGEMENT-MIB - JSR 163 Final Release 1.0
            "

    ::= { standard jsr163(163) 1 }


-- Enterprise OIDs
------------------

--        internet          OBJECT IDENTIFIER ::= { iso(1) org(3) dod(6) 1 }
--        private           OBJECT IDENTIFIER ::= { internet 4 }
--        enterprises       OBJECT IDENTIFIER ::= { private 1 }
	tigase	  	  OBJECT IDENTIFIER ::= { enterprises 16120609 }
	jmgt		  OBJECT IDENTIFIER ::= { tigase products(2) 145 }
	-- experimental      OBJECT IDENTIFIER ::= { jmgt 1 }
  standard          OBJECT IDENTIFIER ::= { jmgt 3 }


-- OBJECT-TYPE OID tree
-----------------------

tigaseMgtMIBObjects
	OBJECT IDENTIFIER ::= { tigaseMgtMIB 1 }
tigaseMgtMIBNotifications
	OBJECT IDENTIFIER ::= { tigaseMgtMIB 2 }
tigaseMgtMIBConformance
	OBJECT IDENTIFIER ::= { tigaseMgtMIB 3 }

TigNum64TC ::= TEXTUAL-CONVENTION
    STATUS       current
    DESCRIPTION
          "This type is based on Counter64, but without its specific
           semantics.
	  "
    SYNTAX Counter64


-- Root OBJECT IDENTIFIER for User group.
--
tigaseUser   OBJECT IDENTIFIER ::= { tigaseMgtMIBObjects 1 }

-- The following objects are mapped from the TigaseUserMBean interface.
-----------------------------------------------------------------------

tigaseUserSessionCount OBJECT-TYPE
    SYNTAX      Gauge32
    MAX-ACCESS  read-only
    STATUS      current
    DESCRIPTION
            "The number of user session currently online on the Tigase server.

	     See tigase.management.TigaseUserMBean.getUserSessionCount()
            "
    REFERENCE "Tigase 4.2 API Specification,
              tigase.management.TigaseUserMBean"
    ::= { tigaseUser 1 }

tigaseUserRegisteredCount OBJECT-TYPE
    SYNTAX      TigNum64TC
    MAX-ACCESS  read-only
    STATUS      current
    DESCRIPTION
            "The total number of user accounts currently registered on the Tigase server.

	     See tigase.management.TigaseUserMBean.getUserRegisteredCount()
            "
    REFERENCE "Tigase 4.2 API Specification,
              tigase.management.TigaseUserMBean"
    ::= { tigaseUser 2 }

-- Root OBJECT IDENTIFIER for Network Connection group.
--
tigaseConnection   OBJECT IDENTIFIER ::= { tigaseMgtMIBObjects 2 }

-- The following objects are mapped from the TigaseConnectionMBean interface.
-----------------------------------------------------------------------

tigaseConnectionClientCount OBJECT-TYPE
    SYNTAX      Gauge32
    MAX-ACCESS  read-only
    STATUS      current
    DESCRIPTION
            "The number of c2s user connections currently active on the Tigase server.

	     See tigase.management.TigaseConnectionMBean.getConnectionClientCount()
            "
    REFERENCE "Tigase 4.2 API Specification,
              tigase.management.TigaseConnectionMBean"
    ::= { tigaseConnection 1 }

tigaseConnectionServerCount OBJECT-TYPE
    SYNTAX      Gauge32
    MAX-ACCESS  read-only
    STATUS      current
    DESCRIPTION
            "The total number of s2s connections currently active on the server.

	     See tigase.management.TigaseConnectionMBean.getConnectionServerCount()
            "
    REFERENCE "Tigase 4.2 API Specification,
              tigase.management.TigaseConnectionMBean"
    ::= { tigaseConnection 2 }

tigaseConnectionBoshCount OBJECT-TYPE
    SYNTAX      Gauge32
    MAX-ACCESS  read-only
    STATUS      current
    DESCRIPTION
            "The number of Bosh user connections currently active on the Tigase server.

	     See tigase.management.TigaseConnectionMBean.getConnectionBoshCount()
            "
    REFERENCE "Tigase 4.2 API Specification,
              tigase.management.TigaseConnectionMBean"
    ::= { tigaseConnection 3 }

-- Root OBJECT IDENTIFIER for Server Load group.
--
tigaseLoad   OBJECT IDENTIFIER ::= { tigaseMgtMIBObjects 3 }

-- The following objects are mapped from the TigaseLoadMBean interface.
-----------------------------------------------------------------------

tigaseLoadSMLastSecond OBJECT-TYPE
    SYNTAX      Gauge32
    MAX-ACCESS  read-only
    STATUS      current
    DESCRIPTION
            "The number of packets processed by Session Manager in last second.

	     See tigase.management.TigaseLoadMBean.getLoadSMLastSecond()
            "
    REFERENCE "Tigase 4.2 API Specification,
              tigase.management.TigaseLoadMBean"
    ::= { tigaseLoad 1 }

tigaseLoadSMLastMinute OBJECT-TYPE
    SYNTAX      Gauge32
    MAX-ACCESS  read-only
    STATUS      current
    DESCRIPTION
            "The number of packets processed by Session Manager in last minute.

	     See tigase.management.TigaseLoadMBean.getLoadSMLastMinute()
            "
    REFERENCE "Tigase 4.2 API Specification,
              tigase.management.TigaseLoadMBean."
    ::= { tigaseLoad 2 }

tigaseLoadSMLastHour OBJECT-TYPE
    SYNTAX      Gauge32
    MAX-ACCESS  read-only
    STATUS      current
    DESCRIPTION
            "The number of packets processed by Session Manager in last hour.

	     See tigase.management.TigaseLoadMBean.getLoadSMLastHour()
            "
    REFERENCE "Tigase 4.2 API Specification,
              tigase.management.TigaseLoadMBean."
    ::= { tigaseLoad 3 }

tigaseLoadMRLastSecond OBJECT-TYPE
    SYNTAX      Gauge32
    MAX-ACCESS  read-only
    STATUS      current
    DESCRIPTION
            "The number of packets processed by Message Router in last second.

	     See tigase.management.TigaseLoadMBean.getLoadMRLastSecond()
            "
    REFERENCE "Tigase 4.2 API Specification,
              tigase.management.TigaseLoadMBean"
    ::= { tigaseLoad 4 }

tigaseLoadMRLastMinute OBJECT-TYPE
    SYNTAX      Gauge32
    MAX-ACCESS  read-only
    STATUS      current
    DESCRIPTION
            "The number of packets processed by Message Router in last minute.

	     See tigase.management.TigaseLoadMBean.getLoadMRLastMinute()
            "
    REFERENCE "Tigase 4.2 API Specification,
              tigase.management.TigaseLoadMBean."
    ::= { tigaseLoad 5 }

tigaseLoadMRLastHour OBJECT-TYPE
    SYNTAX      Gauge32
    MAX-ACCESS  read-only
    STATUS      current
    DESCRIPTION
            "The number of packets processed by Message Router in last hour.

	     See tigase.management.TigaseLoadMBean.getLoadMRLastHour()
            "
    REFERENCE "Tigase 4.2 API Specification,
              tigase.management.TigaseLoadMBean."
    ::= { tigaseLoad 6 }

tigaseLoadMUCLastSecond OBJECT-TYPE
    SYNTAX      Gauge32
    MAX-ACCESS  read-only
    STATUS      current
    DESCRIPTION
            "The number of packets processed by MUC in last second.

	     See tigase.management.TigaseLoadMBean.getLoadMUCLastSecond()
            "
    REFERENCE "Tigase 4.2 API Specification,
              tigase.management.TigaseLoadMBean"
    ::= { tigaseLoad 7 }

tigaseLoadMUCLastMinute OBJECT-TYPE
    SYNTAX      Gauge32
    MAX-ACCESS  read-only
    STATUS      current
    DESCRIPTION
            "The number of packets processed by MUC in last minute.

	     See tigase.management.TigaseLoadMBean.getLoadMUCLastMinute()
            "
    REFERENCE "Tigase 4.2 API Specification,
              tigase.management.TigaseLoadMBean."
    ::= { tigaseLoad 8 }

tigaseLoadMUCLastHour OBJECT-TYPE
    SYNTAX      Gauge32
    MAX-ACCESS  read-only
    STATUS      current
    DESCRIPTION
            "The number of packets processed by MUC in last hour.

	     See tigase.management.TigaseLoadMBean.getLoadMUCLastHour()
            "
    REFERENCE "Tigase 4.2 API Specification,
              tigase.management.TigaseLoadMBean."
    ::= { tigaseLoad 9 }

tigaseLoadPubSubLastSecond OBJECT-TYPE
    SYNTAX      Gauge32
    MAX-ACCESS  read-only
    STATUS      current
    DESCRIPTION
            "The number of packets processed by PubSub in last second.

	     See tigase.management.TigaseLoadMBean.getLoadPubSubLastSecond()
            "
    REFERENCE "Tigase 4.2 API Specification,
              tigase.management.TigaseLoadMBean"
    ::= { tigaseLoad 10 }

tigaseLoadPubSubLastMinute OBJECT-TYPE
    SYNTAX      Gauge32
    MAX-ACCESS  read-only
    STATUS      current
    DESCRIPTION
            "The number of packets processed by PubSub in last minute.

	     See tigase.management.TigaseLoadMBean.getLoadPubSubLastMinute()
            "
    REFERENCE "Tigase 4.2 API Specification,
              tigase.management.TigaseLoadMBean."
    ::= { tigaseLoad 11 }

tigaseLoadPubSubLastHour OBJECT-TYPE
    SYNTAX      Gauge32
    MAX-ACCESS  read-only
    STATUS      current
    DESCRIPTION
            "The number of packets processed by PubSub in last hour.

	     See tigase.management.TigaseLoadMBean.getLoadPubSubLastHour()
            "
    REFERENCE "Tigase 4.2 API Specification,
              tigase.management.TigaseLoadMBean."
    ::= { tigaseLoad 12 }

tigaseLoadS2SLastSecond OBJECT-TYPE
    SYNTAX      Gauge32
    MAX-ACCESS  read-only
    STATUS      current
    DESCRIPTION
            "The number of packets processed by Server Connections Manager in last second.

	     See tigase.management.TigaseLoadMBean.getLoadS2SLastSecond()
            "
    REFERENCE "Tigase 4.2 API Specification,
              tigase.management.TigaseLoadMBean"
    ::= { tigaseLoad 13 }

tigaseLoadS2SLastMinute OBJECT-TYPE
    SYNTAX      Gauge32
    MAX-ACCESS  read-only
    STATUS      current
    DESCRIPTION
            "The number of packets processed by Server Connections Manager in last minute.

	     See tigase.management.TigaseLoadMBean.getLoadS2SLastMinute()
            "
    REFERENCE "Tigase 4.2 API Specification,
              tigase.management.TigaseLoadMBean."
    ::= { tigaseLoad 14 }

tigaseLoadS2SLastHour OBJECT-TYPE
    SYNTAX      Gauge32
    MAX-ACCESS  read-only
    STATUS      current
    DESCRIPTION
            "The number of packets processed by Server Connections Manager in last hour.

	     See tigase.management.TigaseLoadMBean.getLoadS2SLastHour()
            "
    REFERENCE "Tigase 4.2 API Specification,
              tigase.management.TigaseLoadMBean."
    ::= { tigaseLoad 15 }

tigaseLoadC2SLastSecond OBJECT-TYPE
    SYNTAX      Gauge32
    MAX-ACCESS  read-only
    STATUS      current
    DESCRIPTION
            "The number of packets processed by Client Connections Manager in last second.

	     See tigase.management.TigaseLoadMBean.getLoadC2SLastSecond()
            "
    REFERENCE "Tigase 4.2 API Specification,
              tigase.management.TigaseLoadMBean"
    ::= { tigaseLoad 16 }

tigaseLoadC2SLastMinute OBJECT-TYPE
    SYNTAX      Gauge32
    MAX-ACCESS  read-only
    STATUS      current
    DESCRIPTION
            "The number of packets processed by Client Connections Manager in last minute.

	     See tigase.management.TigaseLoadMBean.getLoadC2SLastMinute()
            "
    REFERENCE "Tigase 4.2 API Specification,
              tigase.management.TigaseLoadMBean."
    ::= { tigaseLoad 17 }

tigaseLoadC2SLastHour OBJECT-TYPE
    SYNTAX      Gauge32
    MAX-ACCESS  read-only
    STATUS      current
    DESCRIPTION
            "The number of packets processed by Client Connections Manager in last hour.

	     See tigase.management.TigaseLoadMBean.getLoadC2SLastHour()
            "
    REFERENCE "Tigase 4.2 API Specification,
              tigase.management.TigaseLoadMBean."
    ::= { tigaseLoad 18 }

tigaseLoadBoshLastSecond OBJECT-TYPE
    SYNTAX      Gauge32
    MAX-ACCESS  read-only
    STATUS      current
    DESCRIPTION
            "The number of packets processed by Bosh Connections Manager in last second.

	     See tigase.management.TigaseLoadMBean.getLoadBoshLastSecond()
            "
    REFERENCE "Tigase 4.2 API Specification,
              tigase.management.TigaseLoadMBean"
    ::= { tigaseLoad 19 }

tigaseLoadBoshLastMinute OBJECT-TYPE
    SYNTAX      Gauge32
    MAX-ACCESS  read-only
    STATUS      current
    DESCRIPTION
            "The number of packets processed by Bosh Connections Manager in last minute.

	     See tigase.management.TigaseLoadMBean.getLoadBoshLastMinute()
            "
    REFERENCE "Tigase 4.2 API Specification,
              tigase.management.TigaseLoadMBean."
    ::= { tigaseLoad 20 }

tigaseLoadBoshLastHour OBJECT-TYPE
    SYNTAX      Gauge32
    MAX-ACCESS  read-only
    STATUS      current
    DESCRIPTION
            "The number of packets processed by Bosh Connections Manager in last hour.

	     See tigase.management.TigaseLoadMBean.getLoadBoshLastHour()
            "
    REFERENCE "Tigase 4.2 API Specification,
              tigase.management.TigaseLoadMBean."
    ::= { tigaseLoad 21 }

-- Root OBJECT IDENTIFIER for Tigase System group.
--
tigaseSystem   OBJECT IDENTIFIER ::= { tigaseMgtMIBObjects 4 }

-- The following objects are mapped from the TigaseSystemMBean interface.
-----------------------------------------------------------------------

tigaseSystemHeapTotal OBJECT-TYPE
    SYNTAX      TigNum64TC
    MAX-ACCESS  read-only
    STATUS      current
    DESCRIPTION
      "The total amount of Heap memory in bytes available to the Tigase server.

	     See tigase.management.TigaseSystemMBean.getSystemHeapTotal()
            "
    REFERENCE "Tigase 4.2 API Specification,
              tigase.management.TigaseSystemMBean"
    ::= { tigaseSystem 1 }

tigaseSystemHeapUsed OBJECT-TYPE
    SYNTAX      TigNum64TC
    MAX-ACCESS  read-only
    STATUS      current
    DESCRIPTION
      "The total amount of Heap memory in bytes used by the Tigase server.

	     See tigase.management.TigaseSystemMBean.getSystemHeapUsed()
            "
    REFERENCE "Tigase 4.2 API Specification,
              tigase.management.TigaseSystemMBean"
    ::= { tigaseSystem 2 }

tigaseSystemNonHeapTotal OBJECT-TYPE
    SYNTAX      TigNum64TC
    MAX-ACCESS  read-only
    STATUS      current
    DESCRIPTION
      "The total amount of Non Heap memory in bytes available to the Tigase server.

	     See tigase.management.TigaseSystemMBean.getSystemNonHeapTotal()
            "
    REFERENCE "Tigase 4.2 API Specification,
              tigase.management.TigaseSystemMBean"
    ::= { tigaseSystem 3 }

tigaseSystemNonHeapUsed OBJECT-TYPE
    SYNTAX      TigNum64TC
    MAX-ACCESS  read-only
    STATUS      current
    DESCRIPTION
      "The total amount of Non Heap memory in bytes used by the Tigase server.

	     See tigase.management.TigaseSystemMBean.getSystemNonHeapUsed()
            "
    REFERENCE "Tigase 4.2 API Specification,
              tigase.management.TigaseSystemMBean"
    ::= { tigaseSystem 4 }

tigaseSystemUptimeMillis OBJECT-TYPE
    SYNTAX      TigNum64TC
    MAX-ACCESS  read-only
    STATUS      current
    DESCRIPTION
      "The server uptime in milliseconds.

	     See tigase.management.TigaseSystemMBean.getSystemUptimeMillis()
            "
    REFERENCE "Tigase 4.2 API Specification,
              tigase.management.TigaseSystemMBean"
    ::= { tigaseSystem 5 }

tigaseSystemUptimeHumanReadable OBJECT-TYPE
    SYNTAX      DisplayString
    MAX-ACCESS  read-only
    STATUS      current
    DESCRIPTION
      "The server uptime converted from millis to string representation.

	     See tigase.management.TigaseSystemMBean.getSystemHeapUsed()
            "
    REFERENCE "Tigase 4.2 API Specification,
              tigase.management.TigaseSystemMBean"
    ::= { tigaseSystem 6 }

END
